(defun c:ll ( / lay_chk lay_set)
  (setvar "CMDECHO" 0)
    (setq lay_chk (cdr(assoc 8(entget(car(entsel "\nSelect entity on layer to switch: ")))))
          lay_set (getvar "CLAYER")
    )      
    (while (= lay_chk lay_set)
      (alert "Current layer.")(exit)
    )
    (if (= 0 (cdr (assoc 70 (tblsearch "layer" lay_chk))))
	(progn
; 		(alert "0 lo")
		(command "layer" "lo" lay_chk "")
	)
	(progn
; 		(alert "!0 u")
		(command "layer" "u" lay_chk "")
	)
    )
    (princ)
)
